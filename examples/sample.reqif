# Specification: Telemetry spec

## REQ-006: Packet validation
The system shall reject telemetry packets with invalid checksums before updating the operator display.
- Priority: High
- Verification Method: Test
- Status: Approved

### REQ-007: Operator message wording
The system may show an appropriate warning if practical.
- Status: Draft
